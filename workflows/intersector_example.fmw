FME workspace intersector_example.fmw

Parameters:
- SourceDataset_OGCGEOPACKAGE = /Users/tacree/projects/github-misc/fme_cross_routes/data/road_database.gpkg   # GeoPackage File

Readers:
- OGCGEOPACKAGE_2: OGCGEOPACKAGE from $(SourceDataset_OGCGEOPACKAGE)

Bookmark: Basic Intersector
roads (reader OGCGEOPACKAGE_2)
    attributes: ROUTE text(14), BEGIN_MEASURE double, END_MEASURE double, STREET text(200), id int,PrimaryKey
    -> roads
    -> intersector
intersector: Intersector
    ATTRS_ACCUM_MODE = Use Attributes From One Feature
    CLEANING_TOLERANCE_LOOKUP = 0.01
    DEAGGREGATE_INPUT = Yes
    DIRECTION_NAME = _direction
    GENERATE_LIST_DROP = YES
    IGNORE_HEIGHTS = YES
    LIST_ATTRS_TO_INCLUDE = ROUTE
    LIST_NAME = crossRts
    MEASURE_TYPE_LOOKUP = CONTINUOUS
    NODE_NUM_ATTR = _node_number
    OV_ATTR = _overlaps
    SEPARATE_COLLINEAR_SEGMENTS = No
    CLEANING_TOLERANCE = 0.01
    DUPLICATE_Z_NODES = No
    MEASURE_TYPE = Continuous
    INTERSECTED -> BeginEndMeasureExtractor [extractBegin_Input]
    NODE -> intersected_points
BeginEndMeasureExtractor
    extractEnd_Output -> intersected_segments
intersected_segments: Inspector
intersected_points: Inspector
roads: Inspector

FME custom transformer BeginEndMeasureExtractor

extractBegin_Input (input)
    -> extractBegin
extractBegin: MeasureExtractor
    GET_MODE = VERTEX
    INDEX = 0
    MEASURE_ATTR = BEGIN_MEASURE
    GEOM_TYPE = Individual Vertex by Index
    -> extractEnd
extractEnd: MeasureExtractor
    GET_MODE = VERTEX
    INDEX = -1
    MEASURE_ATTR = END_MEASURE
    GEOM_TYPE = Individual Vertex by Index
    -> AttributeRounder
AttributeRounder
    PLACES = 3
    ROUND_TYPE_TCL = round
    SRC_ATTRS = BEGIN_MEASURE END_MEASURE
    ROUND_TYPE = Nearest
    -> extractEnd_Output (output)
extractEnd_Output (output)
